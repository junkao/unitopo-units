submodule Cisco-IOS-XR-config-cfgmgr-exec-oper-sub1 {

  belongs-to Cisco-IOS-XR-config-cfgmgr-exec-oper {
    prefix Cisco-IOS-XR-config-cfgmgr-exec-oper;
  }

  /*** LINKAGE (IMPORTS / INCLUDES) ***/

  /*** META INFORMATION ***/

  organization "Cisco Systems, Inc.";

  contact
    "Cisco Systems, Inc.
     Customer Service
     Postal: 170 West Tasman Drive
     San Jose, CA 95134
     Tel: +1 800 553-NETS
     E-mail: cs-yang@cisco.com";

  description 
    "This submodule contains a collection of YANG definitions
     for Cisco IOS-XR config-cfgmgr-exec package operational data.

     Copyright (c) 2013-2018 by Cisco Systems, Inc.
     All rights reserved.";

  revision "2017-09-07" {
    description
      "Fixed type translation error.";
  }

  revision "2015-11-09" {
    description
      "IOS XR 6.0 revision.";
  }

  grouping CFGCOMMITLIST-D-ENTRY {
    description "Per Commit Information";
    leaf timestamp {
      type string;
      description "Timestamp";
    }
    leaf commit-id {
      type string;
      description "CommitId";
    }
    leaf user-id {
      type string;
      description "UserId";
    }
    leaf line {
      type string;
      description "Line";
    }
    leaf client-name {
      type string;
      description "Client name";
    }
    leaf label {
      type string;
      description "Label";
    }
    leaf comment {
      type string;
      description "Comment";
    }
  }
}
