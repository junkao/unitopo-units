module Cisco-IOS-XR-mdrv-lib-cfg {

  /*** NAMESPACE / PREFIX DEFINITION ***/

  namespace "http://cisco.com/ns/yang/Cisco-IOS-XR-mdrv-lib-cfg";


  prefix "mdrv-lib-cfg";

  /*** LINKAGE (IMPORTS / INCLUDES) ***/

  import ietf-yang-types { prefix "yang"; }

  import cisco-semver { prefix "semver"; revision-date 2019-03-13; }

  import Cisco-IOS-XR-ifmgr-cfg { prefix "a1"; revision-date 2019-04-05; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mdrv-lib package configuration.

     This module contains definitions
     for the following management objects:
       fast-shutdown: Fast Shutdown configuration

     This YANG module augments the
       Cisco-IOS-XR-ifmgr-cfg
     module with configuration data.

     Copyright (c) 2013-2019 by Cisco Systems, Inc.
     All rights reserved.";

  revision "2019-04-05" {
    description
      "Establish semantic version baseline.";
    semver:module-version "1.0.0";
  }

  revision "2015-11-09" {
    description
      "IOS XR 6.0 revision.";
  }

  container fast-shutdown {
    description "Fast Shutdown configuration";
    leaf ethernet {
      type empty;
      description
        "Enable Fast Shutdown for all Ethernet interfaces";
    }
  }

  augment "/a1:interface-configurations/a1:interface-configuration" {
    leaf fast-shutdown {
      type empty;
      description "Enable Fast Shutdown for this interface";
    }
    description
      "This augment extends the configuration data of
      'Cisco-IOS-XR-ifmgr-cfg'";
  }

  augment "/a1:interface-configurations/a1:interface-configuration" {
    leaf mac-addr {
      type yang:mac-address;
      description "Set the Mac address on an interface";
    }
    description
      "This augment extends the configuration data of
      'Cisco-IOS-XR-ifmgr-cfg'";
  }
}
