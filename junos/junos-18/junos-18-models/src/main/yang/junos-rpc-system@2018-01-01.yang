/*
 * copyright (c) 2018 juniper networks, inc.
 * all rights reserved.
 */
 module junos-rpc-system {
   namespace "http://yang.juniper.net/junos/rpc/system";

   prefix system;

   import junos-common-types {
     prefix jt;
   }

   organization "juniper networks, inc.";

   contact "yang-support@juniper.net";

   description "junos rpc yang module for system command(s)";

   revision 2018-01-01 {
     description "junos: 18.2r1.9";
   }

   rpc get-commit-revision-information {
     description "show latest commit revision number for shared database";
     input {
       leaf level {
         default "brief";
         type enumeration {
           enum "brief" {
             description "display brief output";
           }
           enum "detail" {
             description "display detailed output";
           }
         }
       }
     }
     output {
       choice output_c {
         case output-tag {
           leaf output {
             type string;
           }
         }
         case actual-tag {
           anyxml commit-revision-information;
         }
         case multichassis-tag {
           anyxml multi-routing-engine-results;
         }
       }
     }
   }
 }
